module bookzone-example { 
  yang-version 1.1; 
  namespace 'http://example.com/ns/bookzone'; 
  prefix bz; 

  import ietf-yang-types { 
    prefix yang; 
  } 
  organization 
    "BookZone, a fictive book store chain";
  revision 2025-12-17 { 
    description 
      "Added constraints that 
      - author needs to have an account set before listing a book 
      - number of copies in stock only shows for physical items 
      - makes a book not orderable unless it has a price 
      - book leafrefs are chained correctly 
      Added /users/user/payment-methods and a way to choose which 
      one to use in action purchase."; 
  } 
  revision 2025-12-16 { 
    description 
      "Added status information about books and purchases, see 
      /books/book/popularity 
      /books/book/formats/number-of-copies 
      /users/user/purchase-history 
      Turned reference to book title & format into a grouping, 
      updated references in 
      /users/user/purchase 
      /shipping"; 
  }
  revision 2025-12-15 { 
    description 
      "Added action purchase and notification shipping."; 
  }
  revision 2025-12-11 { 
    description 
      "Added book formats, authors and users, see 
       /books/book/format 
       /authors 
       /users"; 
  } 
  revision 2025-12-09 { 
    description "Initial revision. A catalog of books."; 
  } 
  typedef language-type { 
    type enumeration { 
      enum arabic; 
      enum chinese; 
      enum english; 
      enum french; 
      enum moroccan-arabic; 
      enum swahili; 
      enum swedish; 
      // ...
    } 
    description 
      "Primary language the book consumer needs to master "+ 
      "in order to appreciate the book's content"; 
  } 
  identity format-idty { 
    description "Root identity for all book formats"; 
  } 
  identity paper { 
    base format-idty; 
    description "Physical book printed on paper"; 
  } 
  identity audio-cd { 
    base format-idty; 
    description "Audiobook delivered as Compact Disc"; 
  } 
  identity file-idty { 
    base format-idty; 
    description "Book delivered as a file"; 
  } 
  identity paperback { 
    base paper; 
    description "Physical book with soft covers"; 
  } 
  identity hardcover { 
    base paper; 
    description "Physical book with hard covers"; 
  } 
  identity mp3 { 
    base file-idty; 
    description "Audiobook delivered as MP3 file"; 
  } 
  identity pdf { 
    base file-idty; 
    description "Digital book delivered as PDF file"; 
  } 
  identity epub { 
    base file-idty; 
    description "Digital book delivered as EPUB file"; 
  } 
  typedef ISBN-10-or-13 { 
    type union { 
      type string { 
        length 10; 
        pattern '[0-9]{9}[0-9X]'; 
      } 
      type string { 
        length 13; 
        pattern '97[89][0-9]{10}'; 
      } 
    } 
    description 
      "The International Standard Book Number (ISBN) is a unique 
       numeric commercial book identifier. 
       An ISBN is assigned to each edition and variation (except 
       reprintings) of a book. [source: wikipedia]"; 
    reference 
"https://en.wikipedia.org/wiki/International_Standard_Book_Number";
  } 
  grouping title-format-ref { 
    leaf title { 
      type leafref { 
        path /books/book/title; 
      } 
    } 
    leaf format { 
      type leafref { 
        path /books/book[title=current()/../title]/format/format-id; 
      } 
    } 
  } 
  notification shipping { 
    leaf user { 
      type leafref { 
        path /users/user/name; 
      } 
    } 
    uses title-format-ref;
    leaf number-of-copies { 
      type uint32; 
    } 
  }
  container authors { 
    list author { 
      key name; 
      leaf name { 
        type string; 
      } 
      leaf account-id { 
        type uint32 { 
          range 1001..max; 
        } 
      } 
    } 
  } 
  container books { 
    list book { 
      key title; 
      leaf title { 
        type string; 
      } 
      leaf author { 
        mandatory true;
        type leafref { 
          path /authors/author/name; 
        } 
        must 'deref(current())/../account-id' { 
          error-message 
            "This author does not yet have an account-id defined. 
            Books cannot be added for authors lacking one. 
            The Finance Department is responsible for assigning 
            account-id's to authors."; 
        }
      } 
      leaf language { 
        type language-type; 
      } 
      list format { 
        key isbn; 
        unique format-id;
        leaf isbn { 
          type ISBN-10-or-13; 
        } 
        leaf format-id { 
          mandatory true; 
          type identityref { 
            base format-idty; 
          } 
        } 
        leaf price { 
          type decimal64 { 
            fraction-digits 2; 
          } 
          units sim-dollar; 
        } 
        container number-of-copies { 
          when 'not(derived-from(../format-id, "bz:file-idty"))'; 
          config false; 
          leaf in-stock { 
            type uint32; 
          } 
          leaf reserved { 
            type uint32; 
          } 
          leaf available { 
            type uint32; 
          } 
        }
      } 
      leaf popularity { 
        config false; 
        type uint32; 
        units copies-sold/year; 
        description 
          "Number of copies sold in the last 12-month period"; 
      }       
    } 
  } 
  container users { 
    list user { 
      key user-id; 
      leaf user-id { 
        type string; 
      } 
      leaf name { 
        type string; 
      } 
      list purchase-history { 
        config false; 
        key "title format"; 
        uses title-format-ref; 
        leaf transaction-date-time { 
          type yang:date-and-time; 
        } 
        leaf copies { 
          type uint32; 
        } 
      } 
      container payment-methods { 
        list payment-method { 
          key "method id"; 
          leaf method { 
            type enumeration { 
              enum bookone-account; 
              enum credit-card; 
              enum paypal; 
              enum klarna; 
            } 
          } 
          leaf id { 
            type string; 
          } 
        } 
      }
      action purchase { 
        input {
          must "deref(format)/../price>0" { 
            error-message "Item not orderable at this time"; 
          } 
          uses title-format-ref;
          leaf number-of-copies { 
            type uint32 { 
              range 1..999; 
            } 
            default 1;
          }
          container payment { 
            leaf method { 
              type leafref { 
                path ../../../payment-methods/payment-method/method; 
              } 
            } 
            leaf id { 
              type leafref { 
                path "../../../payment-methods/"+ 
                    "payment-method[method=current()/../method]/id";  
              } 
            }
          }
        }
        output { 
          choice outcome { 
            case success { 
              leaf success { 
                type empty; 
                description 
                  "Order received and will be sent to specified user. 
                  File orders are downloadable at the URL given below."; 
              } 
              leaf delivery-url { 
                type string; 
                description 
                  "Download URL for file deliveries."; 
              } 
            } 
            leaf out-of-stock { 
              type empty; 
              description 
                "Order received, but cannot be delivered at this time. 
                A notification will be sent when the item ships."; 
            } 
            leaf failure { 
              type string; 
              description 
                "Order cancelled, for reason stated here."; 
            } 
          } 
        } 
      }
    } 
  } 
}
