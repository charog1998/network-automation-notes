module config-test{
  yang-version 1.1; 
  namespace 'http://example.com/ns/config-test'; 
  prefix ct; 
  
  container test_container { 
    config false;
    list test { 
      key test_key; 
      leaf test_key { 
        config true;
        type string; 
      }  
    } 
  } 
}
